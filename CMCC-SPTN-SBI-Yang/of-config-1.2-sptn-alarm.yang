module of-config-1.2-sptn-alarm {
 namespace 'http://chinamobile.com.cn/sdn/sptn/sbi/schema/alm' ;

 prefix sptn-alm ;

 import of-config-1.2 { prefix of-config; }
 import ietf-yang-types { prefix yang-types; }
 import of-config-1.2-sptn-oam { prefix sptn-oam; }

 organization "SPTN Working Group";
 contact "SPTN OpenFlow Extensions";

 description
 "This version of this YANG Module is made in 2018-05-09. modify alarm-shield into alarm-mask on the version of 2018-05-02.";

 revision 2018-05-09 {
  description
  "This version of this YANG Module is made in 2016/03/29.";
}


typedef severity-classification {
  type enumeration {
    enum critical {
      value 1 ;
      description "severity-classification critical";
    }
    enum major {
      value 2 ;
      description "severity-classification major";
    }
    enum minor {
      value 3 ;
      description "severity-classification minor";
    }
    enum warning {
      value 4 ;
      description "severity-classification warning";
    }
  }
  description "severity classification";
} 
typedef alarm-status {
  type enumeration {
    enum occurred {
      value 1 ;
      description "alarm occurred";
    }
    enum cleared {
      value 2 ;
      description "alarm cleared";
    }
  }
  description "alarm status";
}

grouping alarm-report {
  description "Common elements for alarm lists";

  uses "of-config:OFResourceType" {
   description "Resource-id of the resource raising the alarm - port, MEG, etc." ;
 }      

 list almCodelist {
  key "almcode";
  leaf SequenceNo {
    type uint32 {
      range "1..4294967295";
    }
  }
  leaf almcode {
    type uint32 ;
    description "alarm code" ;
  }
  leaf severity {
    type severity-classification ;
    description "severity classification" ;
  }
  leaf timestamp {
    type "yang-types:timestamp";
    description "the timestamp is the number of seconds since 2000/01/01 00:00:00" ;
  }
  leaf alarm-status {
    type alarm-status ;
    description "alarm status" ;
  }
  leaf description {
    type string {
      length "1..255" ;
    }
    description "the alarm description" ;
  }
}
}


notification current-alarm-report {

  list alarmReportlist {
    key "OFLogicalSwitchId resource-id";
    leaf OFLogicalSwitchId {
      type "of-config:OFConfigId" ;
    }
    uses alarm-report ;
  }
  }  // notification

  notification protection-status-report {

    leaf SequenceNo {
      type uint32 {
        range "1..4294967295";
      }
    }

    uses "of-config:OFResourceType" {
     description "Resource-id of the protection group." ;
   }      

   leaf OFLogicalSwitchId {
    type "of-config:OFConfigId" ;
  }

  uses "sptn-oam:protection-status" ;

  leaf lastWatchportOfSwitcher {
    type uint32 ;
  }

  leaf currentWatchportOfSwitcher {
    type uint32 ;
  }

  }  // notification

  grouping current-alarm-group {
    container current-alarm {
      description "Current alarms for this logical switch";
      config false;
      list alarmlist {
        key "resource-id";
        uses alarm-report;
      }
    } // container

    container alarm-management {
      description
        "alarm management functions.";

      list alarmConfiglist {
        description
        "Alarm mask configuration by alarm type.";
        key "almcode";
        leaf almcode {
            type uint32 ;
              description "alarm code";
            }

        leaf alarm-mask {
            type boolean;
            default "false";
        }
      }
    }
  }

  augment "/of-config:capable-switch/of-config:logical-switches/of-config:switch" {
      uses current-alarm-group;
    

  } // augment

} // module
